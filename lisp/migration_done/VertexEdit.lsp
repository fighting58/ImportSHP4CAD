;;; 정점 추가 및 삭제 도구 (VertexEdit)
(vl-load-com)

(defun C:VERTEX_ADD (/ *error* ent data type p p_on_curve param idx coords new_coords i vla_obj acDoc old_cmdecho pt same_vertex)
  (setq acDoc (vla-get-activedocument (vlax-get-acad-object)))
  (vla-startundomark acDoc)
  (defun *error* (msg)
    (if (not (member msg '("Function cancelled" "quit / exit abort")))
      (princ (strcat "\n오류: " msg))
    )
    (if old_cmdecho (setvar "CMDECHO" old_cmdecho))
    (vla-endundomark acDoc)
    (princ)
  )
  (setq old_cmdecho (getvar "CMDECHO"))
  (setvar "CMDECHO" 0)
  (princ "\n정점 추가 도구 [VA]")
  (setq ent (car (entsel "\n수정할 객체(Line/LWPolyline) 선택: ")))
  (if (not ent) (progn (princ "\n선택된 객체가 없습니다.") (exit)))
  (setq data (entget ent))
  (setq type (cdr (assoc 0 data)))
  (if (= type "LINE")
    (progn (command "_.pedit" ent "_Y" "_X") (setq ent (entlast)) (setq type "LWPOLYLINE"))
  )
  (if (/= type "LWPOLYLINE") (progn (princ "\n지원하지 않는 객체 타입입니다.") (exit)))
  (setq vla_obj (vlax-ename->vla-object ent))
  (while (setq p (getpoint "\n추가할 정점 위치 클릭 (종료: Enter): "))
    (setq coords (vlax-get vla_obj 'Coordinates) same_vertex nil i 0)
    (repeat (/ (length coords) 2)
      (setq pt (list (nth (* i 2) coords) (nth (1+ (* i 2)) coords)))
      (if (<= (distance (list (car p) (cadr p)) pt) 0.0005) (setq same_vertex T))
      (setq i (1+ i))
    )
    (if same_vertex
      (princ "\n기존 정점과 동일한 점(0.0005m 이내)이므로 추가하지 않습니다.")
      (progn
        (setq p_on_curve (vlax-curve-getClosestPointTo vla_obj p))
        (setq param (vlax-curve-getParamAtPoint vla_obj p_on_curve))
        (setq idx (fix (1+ param)))
        (setq coords (vlax-get vla_obj 'Coordinates) new_coords nil i 0)
        (repeat (/ (length coords) 2)
          (if (= i idx) (setq new_coords (append new_coords (list (car p) (cadr p)))))
          (setq new_coords (append new_coords (list (nth (* i 2) coords) (nth (1+ (* i 2)) coords))))
          (setq i (1+ i))
        )
        (if (>= idx (/ (length coords) 2)) (setq new_coords (append new_coords (list (car p) (cadr p)))))
        (vlax-put vla_obj 'Coordinates new_coords)
        (princ "\n정점이 추가되었습니다.")
      )
    )
  )
  (setvar "CMDECHO" old_cmdecho)
  (vla-endundomark acDoc)
  (princ "\n정점 추가를 종료합니다.")
  (princ)
)

(defun C:VERTEX_DEL (/ *error* ent data type p coords new_coords i dist min_dist min_idx vla_obj acDoc old_osmode old_cmdecho pt)
  (setq acDoc (vla-get-activedocument (vlax-get-acad-object)))
  (vla-startundomark acDoc)
  (defun *error* (msg)
    (if (not (member msg '("Function cancelled" "quit / exit abort")))
      (princ (strcat "\n오류: " msg))
    )
    (if old_osmode (setvar "OSMODE" old_osmode))
    (if old_cmdecho (setvar "CMDECHO" old_cmdecho))
    (vla-endundomark acDoc)
    (princ)
  )
  (setq old_osmode (getvar "OSMODE") old_cmdecho (getvar "CMDECHO"))
  (setvar "CMDECHO" 0)
  (setvar "OSMODE" 1)
  (princ "\n정점 삭제 도구 [VD]")
  (setq ent (car (entsel "\n수정할 LWPolyline 선택: ")))
  (if (not ent) (progn (princ "\n선택된 객체가 없습니다.") (exit)))
  (setq data (entget ent) type (cdr (assoc 0 data)))
  (if (/= type "LWPOLYLINE") (progn (princ "\nLWPolyline만 지원합니다.") (exit)))
  (setq vla_obj (vlax-ename->vla-object ent))
  (while (setq p (getpoint "\n삭제할 정점 클릭 (종료: Enter): "))
    (setq coords (vlax-get vla_obj 'Coordinates) min_dist 1e9 min_idx -1 i 0)
    (repeat (/ (length coords) 2)
      (setq pt (list (nth (* i 2) coords) (nth (1+ (* i 2)) coords)))
      (setq dist (distance (list (car p) (cadr p)) pt))
      (if (< dist min_dist) (setq min_dist dist min_idx i))
      (setq i (1+ i))
    )
    (if (<= min_dist 0.005)
      (progn
        (if (<= (/ (length coords) 2) 2)
          (princ "\n오류: 정점이 2개 이하인 객체는 정점을 삭제할 수 없습니다.")
          (progn
            (setq new_coords nil i 0)
            (repeat (/ (length coords) 2)
              (if (/= i min_idx) (setq new_coords (append new_coords (list (nth (* i 2) coords) (nth (1+ (* i 2)) coords)))))
              (setq i (1+ i))
            )
            (vlax-put vla_obj 'Coordinates new_coords)
            (princ (strcat "\n" (itoa (1+ min_idx)) "번 정점이 삭제되었습니다."))
          )
        )
      )
      (princ "\n일치하는 정점을 찾지 못했습니다. (Tolerance: 0.005)")
    )
  )
  (setvar "OSMODE" old_osmode)
  (setvar "CMDECHO" old_cmdecho)
  (vla-endundomark acDoc)
  (princ "\n정점 삭제를 종료합니다.")
  (princ)
)

(princ "\n정점 편집 도구 로드 완료.")
(princ)
